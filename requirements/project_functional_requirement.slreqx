# project_functional_requirement

## FR-1: The system shall model the thermal dynamics of four interconnected rooms. (Functional)
The system shall implement the continuous-time temperature dynamics for four rooms according to the given differential equation. The output shall be a 4×1 temperature vector x = [x1; x2; x3; x4] representing the temperature of each room over time.

## FR-2: The system shall incorporate the external ambient temperature into the thermal model. (Functional)
The system shall accept an outdoor temperature input u and apply its influence through the term bi(u−xi)b_i(u - x_i)bi​(u−xi​) for each room, reflecting the thermal exchange between the indoor and outdoor environment.

## FR-3: The system shall apply heating power effects to rooms with active heaters. (Functional)
For each room, the heating contribution shall be implemented through the term cihic_i h_i​, where h_i ∈ {0,1} represents the heater status (OFF/ON). Heating shall only affect rooms with active heaters.

## FR-4: The controller shall implement a hysteresis-based thermostat for each room. (Functional)
For rooms equipped with a heater, the controller shall apply hysteresis logic:
- If x_i ≤ On_i, the heater shall be turned ON.
- If x_i ≥ Off_i, the heater shall be turned OFF.
- Otherwise, the previous heater state shall be maintained.

## FR-5: The system shall limit the number of simultaneously active heaters to two. (Functional)
At any simulation time, the total number of active heaters shall not exceed two. This constraint reflects the physical limitation of available heating devices.

## FR-6: Each heater shall be assigned to only one room at a time. (Functional)
The system shall ensure that no heater is simultaneously assigned to multiple rooms and that no room receives more than one heater.

## FR-7: The system shall implement heater transfer between rooms according to defined thresholds. (Functional)
If a room without a heater satisfies x_i ≤ Get_i and the temperature difference x_j - x_i ≥ Diff_i with respect to a room holding a heater, the heater shall be transferred from room j to room i.

## FR-8: The system shall initialize simulation states according to specified initial values. (Functional)
The simulation shall begin with predefined initial temperatures (e.g., 16.5°C for all rooms) and initial heater assignments as defined in the project specification.

## FR-9: The system shall provide monitoring signals for analysis and validation. (Functional)
The system shall expose the following outputs:
- Room temperatures (x1..x4)
- Heater status signals (h1..h4)
- Heater allocation indicators (e.g., hasHeater[4×1] or heater positions)

## FR-10: The system shall operate using the provided model parameters. (Functional)
The system shall use the specified thermal parameters (A matrix, b_i, c_i, thresholds, and outdoor temperature) to reproduce consistent simulation results.
