# project_extra_functional_requirement

## SR-1: A safety gateway shall validate controller outputs before applying them to the plant. (Functional)
All heater commands generated by the controller shall pass through a Safety Gateway block that validates and, if necessary, modifies commands before they are applied to the plant model.

## SR-2: The Safety Gateway shall enforce the maximum of two active heaters. (Functional)
If the controller requests activation of more than two heaters, the Safety Gateway shall adjust the commands to ensure that no more than two heaters remain active.

## SR-3: Rooms without assigned heaters shall not be activated. (Functional)
If a heater is not physically assigned to a room, the Safety Gateway shall force its command to OFF, regardless of controller output.

## SR-4: The system shall define a fail-safe response for invalid commands. (Functional)
If invalid or inconsistent commands are detected, the Safety Gateway shall either:
- Turn all heaters OFF, or
- Maintain the last valid heater configuration (recommended).
The selected policy shall be documented.
